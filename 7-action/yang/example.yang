module example {
  namespace "http://example.com/ns/7-action";
  prefix ex;

  import tailf-common { prefix tailf; }

  description
    "Very small example module for demonstrating tailf:action with
     a Python implementation.

     This module defines one container 'tools' with a single action
     'hello'. The action has one input parameter 'name' and returns
     one output leaf 'greeting'. The Python code in bin/action_daemon.py
     implements the actionpoint 'hello-python'.";

  container tools {
    description
      "Utility actions implemented in Python.";

    tailf:action hello {
      tailf:actionpoint hello-python;

      description
        "Say hello from a Python action implementation.
         The output is a single greeting string.";

      input {
        leaf name {
          type string;
          mandatory true;
          description "Name to greet.";
        }
      }

      output {
        leaf greeting {
          type string;
          description "Greeting message generated by Python.";
        }
      }
    }
  }
}
