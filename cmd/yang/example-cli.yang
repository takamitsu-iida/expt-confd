// Example YANG module used by cmd/cli.py.
//
// - RPCs in this module are exposed as CLI commands
//   (hello, add, set-hostname, ping).
// - The "state" container represents operational state that
//   the CLI shows via "show <leaf>".
// - Custom extensions ex:python-handler / ex:cli-usage are
//   consumed by the Python CLI to locate handlers and
//   generate help/usage strings.

module example-cli {
  namespace "urn:example:cli";
  prefix ex;

  organization "Example";
  contact "example@example.com";
  description
    "Example YANG module for a standalone Python CLI.

     It models a very small network device with:

     - rpc hello:         returns a greeting message
     - rpc add:           returns the sum of two integers
     - rpc set-hostname:  sets the (demo) system hostname
     - rpc ping:          simulates a ping and records last target/result
     - container state (config false): operational state that can be
       shown from the CLI via 'show <leaf>'.
    ";

  // Python handler symbol used by the CLI implementation.
  //
  // Each rpc has exactly one ex:python-handler statement whose
  // argument is a "module:function" string (for importlib).
  /* Python handler mapping (module:function) */
  extension python-handler {
    argument "symbol";
    description
      "Python handler in 'module:function' format for CLI implementations.";
  }

  // Human-friendly usage string for the CLI.
  //
  // Each rpc has one ex:cli-usage. The Python CLI uses this
  // value for "help" output and for "<rpc> help".
  /* CLI usage string for each RPC */
  extension cli-usage {
    argument "text";
    description
      "Human-readable CLI usage string for this RPC (shown in help).";
  }

  // Optional CLI completion candidates for a state leaf.
  //
  // The argument is a space-separated list of tokens that will be
  // proposed by the CLI when completing after that leaf, e.g.
  //   show route <TAB>  ->  ipv4 ipv6
  extension cli-completion {
    argument "values";
    description
      "Space-separated completion candidates for CLI after this leaf.";
  }

  // Optional Python handler for a state leaf.
  //
  // If present, the CLI will call this handler when executing
  //   show <leaf> [...]
  // instead of printing the raw value from the internal state dict.
  // The argument is a "module:function" string similar to
  // ex:python-handler used for RPCs.
  extension state-python-handler {
    argument "symbol";
    description
      "Python handler in 'module:function' format for a state leaf.";
  }

  // Argument style hint for an RPC.
  //
  // If set to "positional", the CLI will treat arguments after
  // the RPC name as positional tokens and pass them as a list to
  // the Python handler. The default is "kv" (key=value pairs).
  extension rpc-arg-style {
    argument "style";
    description
      "Hint for CLI argument style: 'positional' or 'kv' (default).";
  }

  revision "2026-02-10" {
    description "Initial revision";
  }

  // --- RPC commands exposed as CLI commands ------------------------

  rpc hello {
    ex:python-handler "cli:rpc_hello";
    ex:cli-usage "hello name=<name>";
    description "Return a greeting message.";
    input {
      leaf name {
        type string;
        description "Name to greet.";
      }
    }
    output {
      leaf greeting {
        type string;
        description "Greeting text.";
      }
    }
  }

  // Simple arithmetic demo RPC.
  rpc add {
    ex:python-handler "cli:rpc_add";
    ex:cli-usage "add x=<int> y=<int>";
    description "Add two integers.";
    input {
      leaf x {
        type int32;
        description "First operand.";
      }
      leaf y {
        type int32;
        description "Second operand.";
      }
    }
    output {
      leaf result {
        type int32;
        description "Sum of x and y.";
      }
    }
  }

  // Demo of a configuration-style RPC that updates operational
  // state (but does NOT touch the real OS hostname).
  rpc set-hostname {
    ex:python-handler "cli:rpc_set_hostname";
    ex:cli-usage "set-hostname hostname=<name>";
    description
      "Set the demo system hostname (does not change the real OS hostname).";
    input {
      leaf hostname {
        type string;
        description "New hostname for this demo device.";
      }
    }
    output {
      leaf result {
        type string;
        description "Result message.";
      }
    }
  }

  // Ping demo RPC.
  //
  // CLI 側では "ping <dest> [count]" の位置引数で受け取り、
  // YANG input では destination / count の 2 つの leaf に対応させる。
  rpc ping {
    ex:python-handler "cli:rpc_ping";
    ex:cli-usage "ping <dest> [count]";
    ex:rpc-arg-style "positional";
    description "Simulate a ping operation and record the last result in state.";
    input {
      leaf destination {
        type string;
        description "Destination host or address.";
      }
      leaf count {
        type uint8;
        default 4;
        description "Number of echo requests (for demo only).";
      }
    }
    output {
      leaf success {
        type boolean;
        description "true if the simulated ping succeeded.";
      }
    }
  }

  // --- Operational state shown by "show <leaf>" -------------------

  // Non-config data that the CLI exposes via:
  //   show <leaf>
  //
  // Each leaf here becomes one key in the internal state dict
  // inside cmd/cli.py (ExampleCli.state).
  container state {
    config false;
    description "Operational state to be displayed with 'show <leaf>'.";

    leaf hostname {
      type string;
      description "Current demo hostname (managed via rpc set-hostname).";
      ex:state-python-handler "cli:state_hostname";
    }

    leaf mgmt-ip {
      type string;
      description "Management IP address (demo value).";
      ex:state-python-handler "cli:state_mgmt_ip";
    }

    leaf last-hello {
      type string;
      description "The last greeting that was returned by rpc 'hello'.";
      ex:state-python-handler "cli:state_last_hello";
    }

    leaf last-add-result {
      type int32;
      description "The last result produced by rpc 'add'.";
      ex:state-python-handler "cli:state_last_add_result";
    }

    leaf last-ping-target {
      type string;
      description "The last destination used with rpc 'ping'.";
      ex:state-python-handler "cli:state_last_ping_target";
    }

    leaf last-ping-success {
      type boolean;
      description "The last success value produced by rpc 'ping'.";
      ex:state-python-handler "cli:state_last_ping_success";
    }

    // Routing state summary. Detailed routes are printed by the
    // CLI via:
    //   show route
    //   show route ipv4
    //   show route ipv6
    leaf route {
      type string;
      // "<CR>" は CLI 側で特別扱いされ、文字は挿入せず
      // 「そのまま Enter で実行できる」ことを示すためだけに
      // 補完リストに表示される。
      ex:cli-completion "<CR> ipv4 ipv6";
      // route leaf にも state-python-handler を付けておくが、
      // 実際の show route 動作は RPC show-route の方を利用する。
      ex:state-python-handler "cli:state_route";
      description
        "Routing table state (see 'show route [ipv4|ipv6]').";
    }
  }
}
